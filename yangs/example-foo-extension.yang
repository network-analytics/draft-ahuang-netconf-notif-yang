module example-foo-extension {
  yang-version 1.1;
  namespace "urn:ietf:params:xml:ns:yang:example-foo-extension";
  prefix fooext;

  import ietf-subscribed-notifications {
    prefix sn;
  }
  import ietf-system-capabilities {
    prefix sysc;
  }
  import ietf-notification-capabilities {
    prefix notc;
  }
  import ietf-yang-structure-ext {
    prefix sx;
  }
  import ietf-yp-notification {
    prefix iypn;
  }

  description
    "Defines a new 'foo' metadata for the notification envelope.";

  // Extending the notification envelope header with a new
  // 'foo' metadata
  sx:augment-structure "/iypn:envelope" {
    leaf foo {
      type string;
      description
        "Description of the 'foo' extension.";
    }
  }

  // Extending the notifications capabilities so that clients can
  // learn whether this new extension is supported or not
  augment "/sysc:system-capabilities"
        + "/notc:subscription-capabilities"
        + "/iypn:notification-metadata/iypn:metadata" {
    description
      "Extension to the subscription-capabilities model to enable
       clients to learn whether the publisher supports the new
       'foo' metadata.";
    leaf foo {
      type boolean;
      default "false";
      description
        "Adds the 'foo' capability.";
    }
  }

  // (Optional) A user can optionally add knobs for enabling and
  // disabling specific metadata.
  augment "/sn:subscriptions/iypn:metadata" {
    description
      "An user can optionally, support a configuration knob for enabling
       or disabling a metadata.";
    leaf foo {
      type boolean;
      default "false";
      description
        "Configuration knob for enabling and disabling the 'foo' metadata.";
    }
  }
}
