module ietf-notification-envelope {
  yang-version 1.1;
  namespace "urn:ietf:params:xml:ns:netconf:notification:2.0";
  prefix inotifc;
  import ietf-yang-types {
    prefix yang;
    reference
      "RFC 6991: Common YANG Data Types";
  }
  import ietf-subscribed-notifications {
    prefix sn;
    reference
      "RFC 8639: Subscription to YANG Notifications";
  }

  organization "IETF NETCONF (Network Configuration) Working Group";
  contact
    "WG Web:   <https://datatracker.ietf.org/group/netconf/>
     WG List:  <mailto:netconf@ietf.org>

     Authors:  Alex Huang Feng
               <mailto:alex.huang-feng@insa-lyon.fr>
               Pierre Francois
               <mailto:pierre.francois@insa-lyon.fr>
               Thomas Graf
               <mailto:thomas.graf@swisscom.com>
               Benoit Claise
               <mailto:benoit.claise@huawei.com>";

  description
    "Defines a Notification structure for Subscribed Notifications
    [RFC8639] and YANG-Push [RFC8641]. When this Notification header
    is enabled through a configuration, the root container of the 
    notification is defined by the 
    
    This module can be used to validate XML encoded notifications
    [RFC7950], JSON encoded messages [RFC7951] and CBOR encoded
    messages [RFC9254]. Refer to Section Y of RFC XXXX for more
    details.

    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.";

  revision 2024-06-17 {
    description
      "First revision";
    reference
      "RFC XXXX: YANG-Push Notification Container";
  }

  feature notification-envelope {
    description
      "Indicates that YANG-Push supports the notification-envelope
      as defined in RFC XXXX.";
  }

  grouping notif-env-configuration {
    description
      "This grouping defines the configuration switches for
      enabling the notification-envelope defined in RFC XXXX
      and the different supported metadata.";
    leaf enable-notification-envelope {
      if-feature notification-envelope;
      type boolean;
      default false;
      description
        "Enables YANG-Push to use the notification-envelope 
        defined in RFC XXXX. When enabled, the base metadata
        is sent along with the notification contents.";
    }
    container metadata {
      description 
        "Container for configuring optional metadata.";
    }
  }

  notification notification-envelope {
    leaf event-time {
      type yang:date-and-time;
      mandatory true;
      description
        "The date and time the event was generated by the event
        source. This parameter is of type dateTime and compliant
        to [RFC3339].";
    }
    leaf some-other-metadata {
      type string;
      mandatory true;
      description 
        "Some metadata";
    }
    anydata notification-contents {
      description 
        "This contains the values defined by the 'notification'
        statement unchanged.";
    }
  }

  // Subscription container
  augment "/sn:subscriptions/sn:subscription" {
    description
      "This augmentation adds the configuration switches for
      enabling the notification envelope and metadatas.";
    uses notif-env-configuration;
  }
  // Subscription RPCs
  augment "/sn:establish-subscription/sn:input" {
    description
      "This augmentation adds the configuration switches for
      enabling the notification envelope and other metadatas
      during the 'establish-subscription' RPC.";
    uses notif-env-configuration;
  }
  augment "/sn:modify-subscription/sn:input" {
    description
      "This augmentation adds the configuration switches for
      enabling the notification envelope and other metadatas
      during the 'establish-subscription' RPC.";
    uses notif-env-configuration;
  }
}
