module ietf-yp-observation {
  yang-version 1.1;
  namespace "urn:ietf:params:xml:ns:yang:ietf-yp-observation";
  prefix iypo;

  import ietf-yang-types {
    prefix yang;
    reference
      "RFC 9911: Common YANG Data Types";
  }
  import ietf-yang-push {
    prefix yp;
    reference
      "RFC 8641: Subscription to YANG Notifications for Datastore
       Updates";
  }
  import ietf-system-capabilities {
    prefix sysc;
    reference
      "RFC 9196: YANG Modules Describing Capabilities for
       Systems and Datastore Update Notifications";
  }
  import ietf-notification-capabilities {
    prefix notc;
    reference
      "RFC 9196: YANG Modules Describing Capabilities for
       Systems and Datastore Update Notifications";
  }

  organization
    "IETF NETCONF (Network Configuration) Working Group";
  contact
    "WG Web:   <https://datatracker.ietf.org/group/netconf/>
     WG List:  <mailto:netconf@ietf.org>

     Authors:  Thomas Graf
               <mailto:thomas.graf@swisscom.com>
               Benoit Claise
               <mailto:benoit@everything-ops.net>
               Alex Huang Feng
               <mailto:alex.huang-feng@t-systems.com>";
  description
    "Defines YANG-Push event notification header with the observation
     time in streaming update notifications.

     Copyright (c) 2026 IETF Trust and the persons identified as
     authors of the code.  All rights reserved.

     Redistribution and use in source and binary forms, with or without
     modification, is permitted pursuant to, and subject to the license
     terms contained in, the Revised BSD License set forth in Section
     4.c of the IETF Trust's Legal Provisions Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-09-25 {
    description
      "Initial version.";
    reference
      "RFC XXXX: Extensible YANG Model for YANG-Push Notifications";
  }

  grouping yang-push-observation {
    description
      "This grouping adds the observation timestamp for the
       observed metrics.";
    reference
      "Section 3.3.1 of RFC XXXX.";
    leaf timestamp {
      type yang:date-and-time;
      description
        "The point in time at which the reported data was observed.
         The 'point-in-time' leaf states which point in time this
         is.";
    }
    leaf point-in-time {
      type enumeration {
        enum current-accounting {
          description
            "For periodic subscriptions, the point-in-time
             where the metrics are being polled and observed.";
        }
        enum initial-state {
          description
            "For the initial 'push-update' notification of an
             on-change subscription with 'sync-on-start' set to
             'true', the point in time when the reported state was
             last observed to change.  This point in time can precede
             the establishment of the subscription.";
        }
        enum state-changed {
          description
            "For on-change subscriptions, the point in time when the
             state change was observed after the subscription was
             established.";
        }
      }
      description
        "This describes at which point in time the metrics were
         observed.";
    }
  }

  // Event notifications
  augment "/yp:push-update" {
    description
      "This augmentation adds the observation timestamp of the
       accounted metrics in the push-update notification.";
    uses yang-push-observation;
  }

  augment "/yp:push-change-update" {
    description
      "This augmentation adds the observation timestamp of the
       event in the push-change-update notification.";
    uses yang-push-observation;
  }

  // Event capabilities
  augment "/sysc:system-capabilities"
        + "/notc:subscription-capabilities" {
    description
      "Add YANG-Push notification capabilities to system-level
       capability container.";
    leaf yang-push-observation-time-supported {
      type boolean;
      default "false";
      description
        "Specifies whether the publisher supports exporting
         observation-timestamp and point-in-time in notifications.
         If set to true, the publisher supports the
         observation-timestamp and point-in-time in notifications.
         If set to false, these are not supported.";
      reference
        "Section 3.3.1 of RFC XXXX.";
    }
  }
}
