module ietf-notification-envelope {
  yang-version 1.1;
  namespace "urn:ietf:params:xml:ns:netconf:notification:2.0";
  prefix inotenv;
  import ietf-yang-types {
    prefix yang;
    reference
      "RFC 6991: Common YANG Data Types";
  }
  import ietf-inet-types {
    prefix inet;
    reference
      "RFC 6991: Common YANG Data Types";
  }
  import ietf-subscribed-notifications {
    prefix sn;
    reference
      "RFC 8639: Subscription to YANG Notifications";
  }
  import ietf-system-capabilities {
    prefix sysc;
    reference
      "RFC 9196: YANG Modules Describing Capabilities for
       Systems and Datastore Update Notifications";
  }
  import ietf-notification-capabilities {
    prefix notc;
    reference
      "RFC 9196: YANG Modules Describing Capabilities for
       Systems and Datastore Update Notifications";
  }

  organization "IETF NETCONF (Network Configuration) Working Group";
  contact
    "WG Web:   <https://datatracker.ietf.org/group/netconf/>
     WG List:  <mailto:netconf@ietf.org>

     Authors:  Alex Huang Feng
               <mailto:alex.huang-feng@insa-lyon.fr>
               Pierre Francois
               <mailto:pierre.francois@insa-lyon.fr>
               Thomas Graf
               <mailto:thomas.graf@swisscom.com>
               Benoit Claise
               <mailto:benoit.claise@huawei.com>";

  description
    "Defines a Notification structure for Subscribed Notifications
    [RFC8639] and YANG-Push [RFC8641]. When this Notification header
    is enabled through a configuration, the root container of the 
    notification is defined by the 
    
    This module can be used to validate XML encoded notifications
    [RFC7950], JSON encoded messages [RFC7951] and CBOR encoded
    messages [RFC9254]. Refer to Section Y of RFC XXXX for more
    details.

    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.";

  revision 2024-10-14 {
    description
      "First revision";
    reference
      "RFC XXXX: YANG-Push Notification Envelope";
  }

  feature notification-envelope {
    description
      "Indicates that YANG-Push supports the notification-envelope
      as defined in RFC XXXX.";
  }

  feature notification-hostname-sequence-number {
    description
      "Indicates that YANG-Push supports the hostname 
    and sequence-number metadata in the notification-envelope
    as defined in RFC XXXX.";
  }

  feature notification-observation-timestamp {
    description
      "Indicates that YANG-Push supports the sequence-number metadata
    in the notification-envelope as defined in RFC XXXX.";
  }

  grouping notif-env-configuration {
    description
      "This grouping defines the configuration switches for
      enabling the notification-envelope defined in RFC XXXX
      and the different supported metadata.";
    leaf enable-notification-envelope {
      if-feature notification-envelope;
      type boolean;
      default false;
      description
        "Enables YANG-Push to use the notification-envelope 
        defined in RFC XXXX.";
    }
    container metadata {
      description 
        "Container for configuring optional metadata.";
      leaf hostname-sequence-number {
        if-feature notification-hostname-sequence-number;
        type boolean;
        default true;
        description
          "When enabled, hostname and sequence-number is sent
          in the YANG-Push notifications as defined in the
          YANG-Push notification-envelope in RFC XXXX.";
      }
      leaf observation-timestamp {
        if-feature notification-observation-timestamp;
        type boolean;
        default true;
        description
          "When enabled, observation-timestamp and 
          observation-point-in-time is sent in the YANG-Push
          notifications as defined in the YANG-Push
          notification-envelope in RFC XXXX.";
      }
    }
  }

  grouping notif-env-capabilities {
    description
      "This grouping defines the capabilities for
      the notification-envelope defined in RFC XXXX
      and the different supported metadata.";
    leaf notification-envelope {
      if-feature notification-envelope;
      type boolean;
      description
        "Supports YANG-Push to use the notification-envelope 
        defined in RFC XXXX.";
    }
    container metadata {
      description 
        "Container with the supported optional metadata by the
        YANG-Push publisher.";
      leaf hostname-sequence-number {
        if-feature notification-hostname-sequence-number;
        type boolean;
        description
          "Supports hostname and sequence-number
          in the YANG-Push notifications as defined in the
          YANG-Push notification-envelope in RFC XXXX.";
      }
      leaf observation-timestamp {
        if-feature notification-observation-timestamp;
        type boolean;
        description
          "Supports observation-timestamp and 
          observation-point-in-time in the YANG-Push
          notifications as defined in the YANG-Push
          notification-envelope in RFC XXXX.";
      }
    }
  }

  notification notification-envelope {
    leaf event-time {
      type yang:date-and-time;
      mandatory true;
      description
        "The date and time the event was generated by the event
        source. This parameter is of type dateTime and compliant
        to [RFC3339].";
    }
    leaf hostname {
      if-feature notification-hostname-sequence-number;
      type inet:host;
      description
        "The hostname of the network node according to
        [RFC1213]. This value is usually configured on the node
        by the administrator to uniquely identify the node in
        the network.";
    }
    leaf sequence-number {
      if-feature notification-hostname-sequence-number;
      type yang:counter32;
      description
        "Unique sequence number as described in [RFC9187] for each
        published message.";
    }
    leaf observation-timestamp {
      if-feature notification-observation-timestamp;
      type yang:date-and-time;
      description
        "This is the time when events or metrics were observed.";
    }
    leaf observation-point-in-time {
      if-feature notification-observation-timestamp;
      type enumeration {
        enum current-accounting {
          description
            "For periodical subscriptions, the 
            observation-point-in-time where the metrics are being polled
            and observed.";
        }
        enum initial-state {
          description
            "For 'on-change sync on start' subscriptions, the
            initial point in time when the subscription was established
            and the state was observed.";
        }
        enum state-changed {
          description
            "For 'on-change sync on start' subscriptions, the
            point in time when the state change was observed after the
            subscription was established.";
        }
      }
      description
        "This describes at which point in time the metrics were observed";
    }
    anydata notification-contents {
      description 
        "This contains the values defined by the 'notification'
        statement unchanged.";
    }
  }

  // Subscription container
  augment "/sn:subscriptions/sn:subscription" {
    description
      "This augmentation adds the configuration switches for
      enabling the notification envelope and metadatas.";
    uses notif-env-configuration;
  }
  // Subscription RPCs
  augment "/sn:establish-subscription/sn:input" {
    description
      "This augmentation adds the configuration switches for
      enabling the notification envelope and other metadatas
      during the 'establish-subscription' RPC.";
    uses notif-env-configuration;
  }
  augment "/sn:modify-subscription/sn:input" {
    description
      "This augmentation adds the configuration switches for
      enabling the notification envelope and other metadatas
      during the 'establish-subscription' RPC.";
    uses notif-env-configuration;
  }

  // YANG-Push Capabilities extension
  augment "/sysc:system-capabilities/notc:subscription-capabilities" {
    description
      "Extension to the subscription-capabilities model to enable
      clients to learn whether the publisher supports the 
      notification-envelope";

    container notification-metadata {
      description 
        "Adds the notification metadata capabilities to subscription
        capabilities.";
      uses notif-env-capabilities;
    }
  }
}
