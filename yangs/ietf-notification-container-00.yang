module ietf-notification-container {
  yang-version 1.1;
  namespace "urn:ietf:params:xml:ns:netconf:notification:2.0";
  prefix inotifc;
  import ietf-yang-types {
    prefix yang;
    reference
      "RFC 6991: Common YANG Data Types";
  }

  organization "IETF NETCONF (Network Configuration) Working Group";
  contact
    "WG Web:   <https://datatracker.ietf.org/group/netconf/>
     WG List:  <mailto:netconf@ietf.org>

     Authors:  Alex Huang Feng
               <mailto:alex.huang-feng@insa-lyon.fr>
               Pierre Francois
               <mailto:pierre.francois@insa-lyon.fr>
               Thomas Graf
               <mailto:thomas.graf@swisscom.com>
               Benoit Claise
               <mailto:benoit.claise@huawei.com>";

  description
    "Defines a Notification structure for Subscribed Notifications
    [RFC8639] and YANG-Push [RFC8641]. When this Notification header
    is enabled through a configuration, the root container of the 
    notification is defined by the 
    
    This module can be used to validate XML encoded notifications
    [RFC7950], JSON encoded messages [RFC7951] and CBOR encoded
    messages [RFC9254]. Refer to Section Y of RFC XXXX for more
    details.

    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.";

  revision 2024-06-17 {
    description
      "First revision";
    reference
      "RFC XXXX: YANG-Push Notification Container";
  }

  container notification-container {
    leaf eventTime {
      type yang:date-and-time;
      mandatory true;
      description
        "The date and time the event was generated by the event
        source. This parameter is of type dateTime and compliant
        to [RFC3339]. Implementations must support time zones.
        The leaf name in camel case matches the name of the XSD
        element defined in Section 4 of RFC5277.";
    }
    anydata notification-contents {
      description 
        "This contains the values defined by the 'notification' statement
        unchanged.";
    }
  }
}
