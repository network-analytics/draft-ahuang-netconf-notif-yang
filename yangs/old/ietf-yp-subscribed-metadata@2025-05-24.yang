module ietf-yp-subscribed-metadata {
  yang-version 1.1;
  namespace
    "urn:ietf:params:xml:ns:yang:ietf-yp-subscribed-metadata";
  prefix ypsm;
  import ietf-yang-push {
    prefix yp;
    reference
      "RFC 8641: Subscription to YANG Notifications for Datastore Updates";
  }
  import ietf-system-capabilities {
    prefix sysc;
    reference
      "RFC 9196: YANG Modules Describing Capabilities for
       Systems and Datastore Update Notifications";
  }
  import ietf-notification-capabilities {
    prefix notc;
    reference
      "RFC 9196: YANG Modules Describing Capabilities for
       Systems and Datastore Update Notifications";
  }
  organization "IETF NETCONF (Network Configuration) Working Group";
  contact
    "WG Web:   <http:/tools.ietf.org/wg/netconf/>
     WG List:  <mailto:netconf@ietf.org>

     Authors:  Thomas Graf
               <mailto:thomas.graf@swisscom.com>
               Benoit Claise
               <mailto:benoit.claise@huawei.com>
               Alex Huang Feng
               <mailto:alex.huang-feng@insa-lyon.fr>";

  description
    "Defines YANG-Push event notification header with the subscribed
    metadata in streaming update notifications.

    Copyright (c) 2025 IETF Trust and the persons identified as
    authors of the code.  All rights reserved.

    Redistribution and use in source and binary forms, with or without
    modification, is permitted pursuant to, and subject to the license
    terms contained in, the Revised BSD License set forth in Section
    4.c of the IETF Trust's Legal Provisions Relating to IETF Documents
    (https://trustee.ietf.org/license-info).

    This version of this YANG module is part of RFC XXXX; see the RFC
    itself for full legal notices.";

  revision 2025-05-24 {
    description
      "First revision";
    reference
      "RFC XXXX: Support of YANG-Push Notifications Observation Time";
  }

  feature yang-push-subscribed-metadata {
    description
      "This feature indicates the YANG-push Notifications support
      the subscribed metadata in streaming update notifications.";
  }

  // Event notifications
  augment "/yp:push-update" {
    description
      "This augmentation adds the subscribed metadata of the accounted
			metrics in the push-update notification.";
    uses yp:selection-filter-objects {
      refine "selection-filter/within-subscription" {
        description
          "Specifies the selection filter and where it originated
           from. If the 'selection-filter-ref' is populated, the
           filter in the subscription came from the 'filters'
           container. Otherwise, it is populated in-line as part
           of the subscription itself.";
      }
    }
  }

  augment "/yp:push-change-update" {
    description
      "This augmentation adds the subscribed metadata of the event 
      in the push-change-update notification.";
    uses yp:selection-filter-objects {
      refine "selection-filter/within-subscription" {
        description
          "Specifies the selection filter and where it originated
           from. If the 'selection-filter-ref' is populated, the
           filter in the subscription came from the 'filters'
           container. Otherwise, it is populated in-line as part
           of the subscription itself.";
      }
    }
  }

  // Event capabilities
  augment "/sysc:system-capabilities/notc:subscription-capabilities" {
    description
      "Add system level capabilities";
    leaf yang-push-subscribed-metadata-supported {
      if-feature "yang-push-subscribed-metadata";
      type boolean;
      description
        "Specifies whether the publisher supports exporting
        YANG-Push data store, selection filter and YANG library content
				in notifications.";
      reference
        "RFC XXXX: Extensible YANG Model for YANG-Push Notifications";
    }
  }
}
